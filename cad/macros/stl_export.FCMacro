# To run this script, you must have numpy-stl installed system-wide, with its' "stl2bin" binary.
import os.path
import os
import Mesh
import subprocess
import sys

# Go up into the macros directory, and from there to the "cad" directory.
base_file_path = os.path.abspath(os.path.dirname(os.path.dirname(__file__)))
base_export_path = os.path.join(base_file_path, "export/")
export_list = []
# Size in MB above which we won't include a .STL, and just opt for a .3mf instead.
stl_file_size_culling_threshold = 100000000

mesh_export_tolerance = 0.1

pows_of_two = [1, 2, 4, 8]
beam_heights = [1, 2, 3, 6, 12, 24, 48]
beam_tapers = [1, 2]

thru_beam_height_cutoff = 6
hex_key_beam_height_cutoff = 5

clearance_levels = [("close", "1.0"), ("default", "1.25"), ("easy", "1.5"), ("forgiving", "1.75")]

# Assumes that the filename, the object to export, and the exported name prefix
# are all the same
def add_single_object_file(object_name):
    global export_list
    export_list.append((object_name, [(object_name, object_name, object_name)]))
    
def export_object(document, object, folder_name, export_name):
    object.touch()
    document.recompute()

    # Create container directory if it doesn't exist
    folder_path = os.path.join(base_export_path, folder_name) 
    if not os.path.exists(folder_path):
        os.makedirs(folder_path)
    
    # First, export an ASCII .stl
    stl_path = os.path.join(folder_path, export_name + ".stl")
    object.Shape.exportStl(stl_path + "ascii")

    # Convert ASCII .stl to binary
    # TODO: This assumes we're running from a Linux Flatpak, generalize.
    subprocess.run("flatpak-spawn --host stl2bin " + stl_path + "ascii " + stl_path,
                              shell=True, capture_output=True)
    os.remove(stl_path + "ascii")
  
    # Retcon and remove it if it turns out to be too big.
    if os.path.getsize(stl_path) > stl_file_size_culling_threshold:
        os.remove(stl_path)

    # Export a .3mf
    mfmfmf_path = os.path.join(folder_path, export_name + ".3mf")
    shape = object.Shape

    # Compile the mesh
    mesh = Mesh.Mesh()
    vertices, facets = shape.tessellate(mesh_export_tolerance)
    mesh_data = []
    for facet in facets:
        triangle = [vertices[facet[0]], vertices[facet[1]], vertices[facet[2]]]
        mesh_data.append(triangle)
    mesh.addFacets(mesh_data)

    mesh.write(mfmfmf_path)

add_single_object_file("backing_clipped")
add_single_object_file("backing_nubbed")

add_single_object_file("beam_bolted_keyaccess_printable")
add_single_object_file("beam_thru_printable")

add_single_object_file("cover_clipped")
add_single_object_file("cover_nubbed")

add_single_object_file("cornercap_inside")
add_single_object_file("cornercap_outside")

add_single_object_file("cornerstackingcap")
add_single_object_file("cornerstackingcap_thin")

add_single_object_file("corner_printable")

add_single_object_file("cross_glide")
add_single_object_file("cross_slide")

add_single_object_file("gridfinitybaseplatebolton")
add_single_object_file("gridfinitybinbasebolton")

add_single_object_file("hinge")

add_single_object_file("opengridbaseplatebolton")
add_single_object_file("opengridsnapbolton")
add_single_object_file("plate_printable")

add_single_object_file("plug_nubbed_standalone")
add_single_object_file("plug_clipped")

add_single_object_file("glidebolton_intruding")
add_single_object_file("glidebolton_protruding")
add_single_object_file("slidebolton_intruding")
add_single_object_file("slidebolton_protruding")

add_single_object_file("stackinglip_protruding")
add_single_object_file("stackinglip_intruding")

add_single_object_file("stackingpeg")

add_single_object_file("tee_slide_intruding_printable")
add_single_object_file("tee_glide_intruding_printable")
add_single_object_file("tee_slide_protruding_printable")
add_single_object_file("tee_glide_protruding_printable")

add_single_object_file("thrunub_printable")

# TODO: Add non-"printable" base models for remixing as a toggleable option
# TODO: Also add laser cut and routing exports

sheet_doc_path = os.path.join(base_file_path, "sheet.FCStd")
sheet_doc = FreeCAD.openDocument(sheet_doc_path)
dims_object = sheet_doc.getObjectsByLabel("dims")[0]
clearance_multiplier_cell = dims_object.getCellFromAlias("clearancemultiplier")

for file_name, object_list in export_list:
    for clearance_level_name, clearance_level in clearance_levels:
        # Set clearance level in spreadsheet
        dims_object.set(clearance_multiplier_cell, clearance_level)

        # Open file and recompute
        file_path = os.path.join(base_file_path, file_name + ".FCStd")
        doc = FreeCAD.openDocument(file_path)
        doc.recompute()
        
        # Export objects from document
        for folder_name, object_name, export_name in object_list:
            # Prepend clearance level name to folder and export names.
            folder_name = clearance_level_name + "_" + folder_name
            export_name = clearance_level_name + "_" + export_name

            object = doc.getObjectsByLabel(object_name)[0]
            properties = dir(object)
            if "LengthInCells" in properties and "WidthInCells" in properties:
                # Plate-like thing
                for length in pows_of_two:
                    object.LengthInCells = length
                    for width in pows_of_two:
                        # Eliminate duplicates
                        if length > width:
                            continue
                        name = export_name + "_" + str(width) + "x" + str(length)
                        object.WidthInCells = width
                        
                        export_object(doc, object, folder_name, name)
                
            elif "LengthInCells" in properties:
                # Corner-like thing
                for length in pows_of_two:
                    object.LengthInCells = length
                    name = export_name + "_" + str(length)
                    
                    export_object(doc, object, folder_name, name)

            elif "LengthInGridfinityCells" in properties and "WidthInGridfinityCells" in properties:
                for length in pows_of_two:
                    if length == 1:
                        continue
                    object.LengthInGridfinityCells = int(length / 2)
                    for width in pows_of_two:
                        # Eliminate duplicates
                        if width == 1 or length > width:
                            continue
                        object.WidthInGridfinityCells = int(width / 2)

                        name = export_name + "_" + str(int(width / 2)) + "x" + str(int(length / 2))
                        export_object(doc, object, folder_name, name)

            elif "TaperLengthInCells" in properties and "TaperWidthInCells" in properties and "HeightInHeightUnits" in properties:
                # Beam-like thing
                for width in beam_tapers:
                    object.TaperWidthInCells = width
                    for length in beam_tapers:
                        object.TaperLengthInCells = length
                        for height in beam_heights:
                            if "beam_bolted_keyaccess" in object_name and height < hex_key_beam_height_cutoff:
                                continue
                            object.HeightInHeightUnits = height
                            name = export_name + "_" + str(height) + "-" + str(width) + "x" + str(length)
                            
                            export_object(doc, object, folder_name, name)
                
            elif "HeightInHeightUnits" in properties:
                # Thru-beam-like thing
                for height in beam_heights:
                    if "beam_thru" in object_name and height > thru_beam_height_cutoff:
                        continue
                    object.HeightInHeightUnits = height

                    name = export_name + "_" + str(height)
                    
                    export_object(doc, object, folder_name, name)
            else:
                # Assume it's just a single stand-alone model.
                export_object(doc, object, folder_name, export_name)
        
        # Close document
        FreeCAD.closeDocument(file_name)
